;;; End-to-end runtime probe for the SWCAD Workflow public commands.

(vl-load-com)

(defun swapp-int-env (name fallback / value)
  (setq value (getenv name))
  (if (or (not value) (= value "")) fallback value)
)

(setq *swapp-int-log-path* nil)

(defun swapp-int-write (ignored text / path handle)
  (setq path (getenv "SWCAD_WORKFLOW_LOG"))
  (if (or (not path) (= path "")) (setq path *swapp-int-log-path*))
  (if path
    (progn
      (setq path (vl-string-translate "\\" "/" path))
      (setq handle (open path "a"))
      (if handle
        (progn
          (write-line (if text text "") handle)
          (close handle)
        )
      )
    )
  )
)

(defun swapp-int-bool (value)
  (if value "yes" "no")
)

(defun swapp-int-source-metadata-ok-p (source records / record bbox expected-stem)
  (setq record (car records))
  (setq bbox (if record (nth 4 record) nil))
  (setq expected-stem (if source (vl-filename-base source) ""))
  (and
    (equal (swapp-state-value "SOURCE_SHEET_STATUS") "CAPTURED_BEFORE_BIND")
    (= (length records) 1)
    (= (nth 0 record) 1)
    (equal (strcase (nth 1 record)) (strcase expected-stem))
    bbox
    (= (length bbox) 4)
    (numberp (nth 0 bbox))
    (numberp (nth 1 bbox))
    (numberp (nth 2 bbox))
    (numberp (nth 3 bbox))
    (< (nth 0 bbox) (nth 2 bbox))
    (< (nth 1 bbox) (nth 3 bbox))
  )
)

(defun swapp-int-write-source-metadata (handle records audit / first)
  (setq first (car records))
  (swapp-int-write handle (strcat "Source metadata state: " (if (swapp-state-value "SOURCE_SHEET_STATUS") (swapp-state-value "SOURCE_SHEET_STATUS") "<none>")))
  (swapp-int-write handle (strcat "Source metadata count: " (itoa (length records))))
  (swapp-int-write handle (strcat "Source metadata first: " (if first (vl-princ-to-string first) "<none>")))
  (swapp-int-write handle (strcat "Source metadata audit: " (swapp-int-bool audit)))
)

(defun swapp-int-write-performance (handle label)
  (swapp-int-write handle (strcat label " elapsed ms: " (itoa *swapp-last-command-elapsed-ms*)))
  (swapp-int-write handle (strcat label " read ms: " (itoa *swapp-last-command-read-ms*)))
  (swapp-int-write handle (strcat label " inventory hits/misses: " (itoa *swapp-last-command-cache-hits*) "/" (itoa *swapp-last-command-cache-misses*)))
  (swapp-int-write handle (strcat label " INSERT full scans: " (itoa *swapp-last-command-title-insert-scans*)))
  (swapp-int-write handle (strcat label " INSERT cache hits: " (itoa *swapp-last-command-title-insert-cache-hits*)))
)

(defun swapp-int-attach (source / result)
  (setq result
    (vl-catch-all-apply
      'vla-AttachExternalReference
      (list
        (swapp-model)
        source
        "SWCAD_WORKFLOW_TEST_XREF"
        (vlax-3d-point '(1000.0 2000.0 0.0))
        1.0 1.0 1.0 0.0
        :vlax-false
      )
    )
  )
  (if (vl-catch-all-error-p result) nil result)
)

(defun swapp-int-command-ok (command / result)
  (setq result (vl-catch-all-apply command nil))
  (not (vl-catch-all-error-p result))
)

(defun swapp-int-definition-path-audit (/ records record workflow-record no-key-count)
  (setq records (nth 2 (swapp-named-definition-snapshot)))
  (setq workflow-record "<missing>")
  (setq no-key-count 0)
  (foreach record records
    (if
      (vl-string-search
        "DICT|NOD/SWCAD_WORKFLOW_STATE|XRECORD|"
        record
      )
      (setq workflow-record record)
    )
    (if (vl-string-search "<NO-KEY>" record)
      (setq no-key-count (1+ no-key-count))
    )
  )
  (list workflow-record no-key-count)
)

(defun swapp-int-main (/ root mode source output log-path handle load-result load-ok attached command-ok status-command-ok status-dbmod-before status-dbmod-after summary xrefs dimensions source-titles source-frames source-records source-metadata-ok evidence native-targets native-target-frames native-target-titles stage dim-state cleanup-state layouts title-status dim-ok cleanup-ok layout-ok verify-command-ok pass unmatched-before unmatched-after unmatched-handle same-handle-after same-handle-before layout-plan wrappers wrapper-index wrapper-record wrappers-before wrappers-after dimensions-before dimensions-after expected-dimensions-after bbox-before bbox-after definition-path-audit)
  (setq root (vl-string-translate "\\" "/" (swapp-int-env "SWCAD_WORKFLOW_ROOT" "C:/Users/DR-DESIGN/Documents/CAD tool")))
  (setq mode (strcase (swapp-int-env "SWCAD_WORKFLOW_MODE" "MATERIALIZE_RAW")))
  (setq source (vl-string-translate "\\" "/" (swapp-int-env "SWCAD_WORKFLOW_SOURCE" "")))
  (setq output (vl-string-translate "\\" "/" (swapp-int-env "SWCAD_WORKFLOW_OUTPUT" "")))
  (setq log-path (vl-string-translate "\\" "/" (swapp-int-env "SWCAD_WORKFLOW_LOG" (strcat root "/work/swcad_workflow_integration_probe.txt"))))
  (setq *swapp-int-log-path* log-path)
  (setq handle (open log-path "w"))
  (if handle (close handle))
  (if handle
    (progn
      (setq handle T)
      (swapp-int-write handle "SWCAD Workflow integration probe")
      (swapp-int-write handle (strcat "Mode: " mode))
      (swapp-int-write handle "Milestone: before app loader")
      (setq load-result
        (vl-catch-all-apply
          'load
          (list (strcat root "/apps/swcad-workflow/swcad_workflow_load.lsp"))
        )
      )
      (setq load-ok (not (vl-catch-all-error-p load-result)))
      (swapp-int-write handle (strcat "Milestone: after app loader=" (if load-ok "OK" "ERROR")))
    )
    (setq handle nil)
  )
  (if handle
    (progn
      (swapp-int-write handle (strcat "Load result: " (if load-ok "OK" "ERROR")))
      (if load-ok
        (cond
          ((equal mode "MATERIALIZE_RAW")
            (swapp-int-write handle "Milestone: before XREF attach")
            (setq attached (swapp-int-attach source))
            (swapp-int-write handle (strcat "Milestone: after XREF attach=" (swapp-int-bool attached)))
            (setq *swcad-title-work-copy-saveas-path-override* output)
            (swapp-int-write handle "Milestone: before public SWCADRUN")
            (setq command-ok (if attached (swapp-int-command-ok 'c:SWCADRUN) nil))
            (swapp-int-write handle (strcat "Milestone: after public SWCADRUN=" (swapp-int-bool command-ok)))
            (setq summary (swcad-title-fast-sheet-summary))
            (setq xrefs (length (swapp-top-xref-references)))
            (setq dimensions (swapp-top-dimension-count))
            (setq source-titles (swcad-title-fast-summary-value summary "source-title-count"))
            (setq source-frames (swcad-title-fast-summary-value summary "source-frame-count"))
            (setq stage (swapp-workflow-stage))
            (setq source-records (swapp-source-sheet-records-read))
            (setq source-metadata-ok (swapp-int-source-metadata-ok-p source source-records))
            (swapp-int-write handle (strcat "Attach result: " (swapp-int-bool attached)))
            (swapp-int-write handle (strcat "Public SWCADRUN result: " (swapp-int-bool command-ok)))
            (swapp-int-write handle (strcat "Remaining XREF count: " (itoa xrefs)))
            (swapp-int-write handle (strcat "Top dimension count: " (itoa dimensions)))
            (swapp-int-write handle (strcat "Source title count: " (itoa source-titles)))
            (swapp-int-write handle (strcat "Source frame count: " (itoa source-frames)))
            (swapp-int-write handle (strcat "Materialized state: " (if (swapp-state-value "MATERIALIZED") (swapp-state-value "MATERIALIZED") "<none>")))
            (swapp-int-write handle (strcat "Workflow stage: " stage))
            (swapp-int-write-source-metadata handle source-records source-metadata-ok)
            (setq pass
              (and
                attached command-ok
                (= xrefs 0)
                (= dimensions 143)
                (= source-titles 15)
                (= source-frames 15)
                (equal (swapp-state-value "MATERIALIZED") "OK")
                (equal stage "TITLE")
                source-metadata-ok
                (findfile output)
              )
            )
          )
          ((equal mode "MATERIALIZE_WRAPPED_XREF")
            (swapp-int-write handle "Milestone: before wrapped XREF attach")
            (setq attached (swapp-int-attach source))
            (swapp-int-write handle (strcat "Milestone: after wrapped XREF attach=" (swapp-int-bool attached)))
            (setq evidence (if attached (swapp-xref-deep-evidence (swapp-top-xref-references)) nil))
            (setq native-targets (if evidence (swapp-evidence-value evidence "target-references") 0))
            (setq native-target-frames (if evidence (swapp-evidence-value evidence "target-frame-references") 0))
            (setq native-target-titles (if evidence (swapp-evidence-value evidence "target-title-references") 0))
            (setq expected-dimensions-after (if evidence (swapp-evidence-value evidence "dimensions") 0))
            (setq bbox-before (swapp-model-bbox))
            (setq *swcad-title-work-copy-saveas-path-override* output)
            (swapp-int-write handle (strcat "Wrapped XREF native guard targets: " (itoa native-targets)))
            (swapp-int-write handle (strcat "Wrapped XREF top target frames/titles: " (itoa native-target-frames) "/" (itoa native-target-titles)))
            (swapp-int-write handle (strcat "Wrapped XREF expected deep dimensions: " (itoa expected-dimensions-after)))
            (swapp-int-write handle "Milestone: before wrapped XREF SWCADRUN")
            (setq command-ok (if attached (swapp-int-command-ok 'c:SWCADRUN) nil))
            (swapp-int-write handle (strcat "Milestone: after wrapped XREF SWCADRUN=" (swapp-int-bool command-ok)))
            (if command-ok (swapp-int-write-performance handle "Public SWCADRUN"))
            (setq summary (swcad-title-fast-sheet-summary))
            (setq xrefs (length (swapp-top-xref-references)))
            (setq wrappers-after (length (swapp-sheet-wrapper-status-records)))
            (setq dimensions (swapp-top-dimension-count))
            (setq bbox-after (swapp-model-bbox))
            (setq source-titles (swcad-title-fast-summary-value summary "source-title-count"))
            (setq source-frames (swcad-title-fast-summary-value summary "source-frame-count"))
            (setq stage (swapp-workflow-stage))
            (setq source-records (swapp-source-sheet-records-read))
            (setq source-metadata-ok (swapp-int-source-metadata-ok-p source source-records))
            (setq status-dbmod-before (getvar "DBMOD"))
            (setq status-command-ok (swapp-int-command-ok 'c:SWCADSTATUS))
            (setq status-dbmod-after (getvar "DBMOD"))
            (if status-command-ok (swapp-int-write-performance handle "Public SWCADSTATUS"))
            (swapp-int-write handle (strcat "Remaining XREF count: " (itoa xrefs)))
            (swapp-int-write handle (strcat "Remaining sheet wrappers: " (itoa wrappers-after)))
            (swapp-int-write handle (strcat "Top dimension count: " (itoa dimensions)))
            (swapp-int-write handle (strcat "Model bbox preserved: " (swapp-int-bool (swapp-bbox-near-p bbox-before bbox-after))))
            (swapp-int-write handle (strcat "Top dimension count matched expected: " (swapp-int-bool (= dimensions expected-dimensions-after))))
            (swapp-int-write handle (strcat "Source title count: " (itoa source-titles)))
            (swapp-int-write handle (strcat "Source frame count: " (itoa source-frames)))
            (swapp-int-write handle (strcat "Materialized state: " (if (swapp-state-value "MATERIALIZED") (swapp-state-value "MATERIALIZED") "<none>")))
            (swapp-int-write handle (strcat "Workflow stage: " stage))
            (swapp-int-write handle (strcat "Public SWCADSTATUS read-only: " (swapp-int-bool (= status-dbmod-before status-dbmod-after))))
            (swapp-int-write-source-metadata handle source-records source-metadata-ok)
            (setq pass
              (and
                attached command-ok
                status-command-ok
                (= *swapp-last-command-title-insert-scans* 1)
                (= status-dbmod-before status-dbmod-after)
                (= native-target-titles 0)
                (= xrefs 0)
                (= wrappers-after 0)
                (= dimensions expected-dimensions-after)
                (= source-titles 30)
                (= source-frames 30)
                (equal (swapp-state-value "MATERIALIZED") "OK")
                (equal stage "TITLE")
                source-metadata-ok
                (findfile output)
              )
            )
          )
          ((equal mode "NATIVE_GUARD")
            (setq attached (swapp-int-attach source))
            (setq evidence (if attached (swapp-xref-deep-evidence (swapp-top-xref-references)) nil))
            (setq native-targets (if evidence (swapp-evidence-value evidence "target-references") 0))
            (setq native-target-frames (if evidence (swapp-evidence-value evidence "target-frame-references") 0))
            (setq native-target-titles (if evidence (swapp-evidence-value evidence "target-title-references") 0))
            (setq command-ok (if attached (swapp-int-command-ok 'c:SWCADRUN) nil))
            (setq xrefs (length (swapp-top-xref-references)))
            (setq stage (swapp-workflow-stage))
            (swapp-int-write handle (strcat "Attach result: " (swapp-int-bool attached)))
            (swapp-int-write handle (strcat "Public SWCADRUN returned without error: " (swapp-int-bool command-ok)))
            (swapp-int-write handle (strcat "Detected deep native target references: " (itoa native-targets)))
            (swapp-int-write handle (strcat "Detected top target frames/titles: " (itoa native-target-frames) "/" (itoa native-target-titles)))
            (swapp-int-write handle (strcat "Remaining XREF count: " (itoa xrefs)))
            (swapp-int-write handle (strcat "Materialized state: " (if (swapp-state-value "MATERIALIZED") (swapp-state-value "MATERIALIZED") "<none>")))
            (swapp-int-write handle (strcat "Workflow stage: " stage))
            (setq pass
              (and
                attached command-ok
                (> native-targets 0)
                (> native-target-frames 0)
                (> native-target-titles 0)
                (= xrefs 1)
                (not (equal (swapp-state-value "MATERIALIZED") "OK"))
                (equal stage "XREF")
              )
            )
          )
          ((equal mode "SHEET_WRAPPERS")
            (setq wrappers (swapp-sheet-wrapper-records))
            (setq wrappers-before (length wrappers))
            (setq dimensions-before (swapp-top-dimension-count))
            (setq expected-dimensions-after
              (+ dimensions-before (swapp-model-expandable-dimension-count))
            )
            (setq bbox-before (swapp-model-bbox))
            (setq xrefs (length (swapp-top-xref-references)))
            (setq stage (swapp-workflow-stage))
            (swapp-int-write handle (strcat "Remaining XREF count before: " (itoa xrefs)))
            (swapp-int-write handle (strcat "Sheet wrappers before: " (itoa wrappers-before)))
            (swapp-int-write handle (strcat "Top dimensions before: " (itoa dimensions-before)))
            (swapp-int-write handle (strcat "Workflow stage before: " stage))
            (swapp-int-write handle (strcat "Expected top dimensions after: " (itoa expected-dimensions-after)))
            (setq wrapper-index 0)
            (foreach wrapper-record wrappers
              (setq wrapper-index (1+ wrapper-index))
              (swapp-int-write
                handle
                (strcat
                  "Wrapper #" (itoa wrapper-index)
                  ": name=" (swapp-sheet-wrapper-value wrapper-record "name")
                  ", frames=" (itoa (swapp-sheet-wrapper-value wrapper-record "frames"))
                  ", titles=" (itoa (swapp-sheet-wrapper-value wrapper-record "titles"))
                  ", native-targets=" (itoa (swapp-sheet-wrapper-value wrapper-record "native-targets"))
                  ", dimensions=" (itoa (swapp-sheet-wrapper-value wrapper-record "dimensions"))
                  ", objects=" (itoa (swapp-sheet-wrapper-value wrapper-record "objects"))
                  ", transform=" (swapp-int-bool (swapp-sheet-wrapper-value wrapper-record "transform-supported"))
                )
              )
            )
            (swapp-int-write handle "Milestone: before sheet-wrapper SWCADRUN")
            (setq command-ok (swapp-int-command-ok 'c:SWCADRUN))
            (swapp-int-write handle (strcat "Milestone: after sheet-wrapper SWCADRUN=" (swapp-int-bool command-ok)))
            (setq wrappers-after (length (swapp-sheet-wrapper-records)))
            (setq dimensions-after (swapp-top-dimension-count))
            (setq bbox-after (swapp-model-bbox))
            (setq summary (swcad-title-fast-sheet-summary))
            (setq source-titles (swcad-title-fast-summary-value summary "source-title-count"))
            (setq source-frames (swcad-title-fast-summary-value summary "source-frame-count"))
            (setq stage (swapp-workflow-stage))
            (swapp-int-write handle (strcat "Public SWCADRUN result: " (swapp-int-bool command-ok)))
            (swapp-int-write handle (strcat "Sheet wrappers after: " (itoa wrappers-after)))
            (swapp-int-write handle (strcat "Top dimensions after: " (itoa dimensions-after)))
            (swapp-int-write handle (strcat "Top dimension count matched expected: " (swapp-int-bool (= dimensions-after expected-dimensions-after))))
            (swapp-int-write handle (strcat "Model bbox preserved: " (swapp-int-bool (swapp-bbox-near-p bbox-before bbox-after))))
            (swapp-int-write handle (strcat "Source title count: " (itoa source-titles)))
            (swapp-int-write handle (strcat "Source frame count: " (itoa source-frames)))
            (swapp-int-write handle (strcat "Sheet wrapper state: " (if (swapp-state-value "SHEET_WRAPPERS") (swapp-state-value "SHEET_WRAPPERS") "<none>")))
            (swapp-int-write handle (strcat "Workflow stage: " stage))
            (setq pass
              (and
                command-ok
                (> wrappers-before 0)
                (= wrappers-after 0)
                (= dimensions-after expected-dimensions-after)
                (swapp-bbox-near-p bbox-before bbox-after)
                (> source-titles 0)
                (> source-frames 0)
                (equal (swapp-state-value "SHEET_WRAPPERS") "OK")
                (equal stage "TITLE")
              )
            )
          )
          ((equal mode "DOWNSTREAM")
            (setq evidence (swapp-title-evidence))
            (setq command-ok (and (swapp-title-complete-p evidence) (swapp-int-command-ok 'c:SWCADRUN)))
            (setq dim-state (swapp-state-value "DIMSTYLE"))
            (setq stage (swapp-workflow-stage))
            (setq layout-plan (if (equal stage "LAYOUT") (swapp-layout-plan) nil))
            (setq command-ok (and command-ok (equal stage "LAYOUT") (swapp-int-command-ok 'c:SWCADRUN)))
            (setq stage (swapp-workflow-stage))
            (setq command-ok (and command-ok (equal stage "CLEANUP") (swapp-int-command-ok 'c:SWCADRUN)))
            (setq cleanup-state (swapp-state-value "RESOURCE_CLEANUP"))
            (setq cleanup-ok (swapp-resource-cleanup-verify))
            (setq definition-path-audit (swapp-int-definition-path-audit))
            (setq stage (swapp-workflow-stage))
            (setq layouts (length (swapp-layout-owned-names)))
            (if command-ok
              (progn
                (setq title-status (swcad-title-integrated-verify-final-summary))
                (setq dim-ok (swapp-dimstyle-verify))
                (setq layout-ok (swapp-layout-state-valid-p (length (swcad-title-frame-records))))
                (swapp-save-current)
              )
              (progn
                (setq title-status "SKIPPED_AFTER_STAGE_FAILURE")
                (setq dim-ok nil)
                (setq layout-ok nil)
              )
            )
            (swapp-int-write handle (strcat "Public SWCADRUN sequence: " (swapp-int-bool command-ok)))
            (swapp-int-write handle (strcat "DIMSTYLE state: " (if dim-state dim-state "<none>")))
            (swapp-int-write handle (strcat "Dimension semantics: " (if (swapp-state-value "DIMENSION_SEMANTICS") (swapp-state-value "DIMENSION_SEMANTICS") "<none>")))
            (swapp-int-write handle (strcat "Dimension restore count: " (if (swapp-state-value "DIMENSION_RESTORE_COUNT") (swapp-state-value "DIMENSION_RESTORE_COUNT") "<none>")))
            (swapp-int-write handle (strcat "Resource cleanup state: " (if cleanup-state cleanup-state "<none>")))
            (swapp-int-write handle (strcat "Resource cleanup zero pass: " (if (swapp-state-value "RESOURCE_CLEANUP_ZERO_PASS") (swapp-state-value "RESOURCE_CLEANUP_ZERO_PASS") "<none>")))
            (swapp-int-write handle (strcat "Resource cleanup definition signature: " (if (swapp-state-value "RESOURCE_CLEANUP_DEFINITION_SIGNATURE") (swapp-state-value "RESOURCE_CLEANUP_DEFINITION_SIGNATURE") "<none>")))
            (swapp-int-write handle (strcat "Resource cleanup definition identity signature: " (if (swapp-state-value "RESOURCE_CLEANUP_DEFINITION_IDENTITY_SIGNATURE") (swapp-state-value "RESOURCE_CLEANUP_DEFINITION_IDENTITY_SIGNATURE") "<none>")))
            (swapp-int-write handle (strcat "Resource cleanup stable definition identity signature: " (if (swapp-state-value "RESOURCE_CLEANUP_STABLE_DEFINITION_IDENTITY_SIGNATURE") (swapp-state-value "RESOURCE_CLEANUP_STABLE_DEFINITION_IDENTITY_SIGNATURE") "<none>")))
            (swapp-int-write handle (strcat "Resource cleanup APPID identity signature: " (if (swapp-state-value "RESOURCE_CLEANUP_APPID_IDENTITY_SIGNATURE") (swapp-state-value "RESOURCE_CLEANUP_APPID_IDENTITY_SIGNATURE") "<none>")))
            (swapp-int-write handle (strcat "Resource cleanup VPORT identity signature: " (if (swapp-state-value "RESOURCE_CLEANUP_VPORT_IDENTITY_SIGNATURE") (swapp-state-value "RESOURCE_CLEANUP_VPORT_IDENTITY_SIGNATURE") "<none>")))
            (swapp-int-write handle (strcat "Resource cleanup session anonymous block identity signature: " (if (swapp-state-value "RESOURCE_CLEANUP_SESSION_ANON_BLOCK_IDENTITY_SIGNATURE") (swapp-state-value "RESOURCE_CLEANUP_SESSION_ANON_BLOCK_IDENTITY_SIGNATURE") "<none>")))
            (swapp-int-write handle (strcat "Resource cleanup state-save stabilization passes: " (if (swapp-state-value "RESOURCE_CLEANUP_STATE_SAVE_STABILIZATION_PASSES") (swapp-state-value "RESOURCE_CLEANUP_STATE_SAVE_STABILIZATION_PASSES") "<none>")))
            (swapp-int-write handle (strcat "Resource cleanup state-save rebase count: " (if (swapp-state-value "RESOURCE_CLEANUP_STATE_SAVE_REBASE_COUNT") (swapp-state-value "RESOURCE_CLEANUP_STATE_SAVE_REBASE_COUNT") "<none>")))
            (swapp-int-write handle (strcat "Resource cleanup audit: " (swapp-int-bool cleanup-ok)))
            (swapp-int-write handle (strcat "Workflow state definition record: " (car definition-path-audit)))
            (swapp-int-write handle (strcat "Definition <NO-KEY> count: " (itoa (cadr definition-path-audit))))
            (swapp-int-write handle (strcat "Layout plan count before create: " (itoa (length layout-plan))))
            (if layout-plan
              (progn
                (swapp-int-write handle (strcat "Layout plan first: " (swapp-layout-plan-item-text (car layout-plan) 1)))
                (swapp-int-write handle (strcat "Layout plan last: " (swapp-layout-plan-item-text (car (reverse layout-plan)) (length layout-plan))))
              )
            )
            (if (equal (swapp-state-value "DIMENSION_SEMANTICS") "CHANGED")
              (progn
                (setq unmatched-before (swapp-first-unmatched-semantic *swapp-last-dimension-semantics-before* *swapp-last-dimension-semantics-after*))
                (setq unmatched-after (swapp-first-unmatched-semantic *swapp-last-dimension-semantics-after* *swapp-last-dimension-semantics-before*))
                (setq unmatched-handle (swapp-semantic-record-handle unmatched-before))
                (setq same-handle-after (swapp-semantic-by-handle unmatched-handle *swapp-last-dimension-semantics-after*))
                (setq same-handle-before (swapp-semantic-by-handle (swapp-semantic-record-handle unmatched-after) *swapp-last-dimension-semantics-before*))
                (swapp-int-write handle (strcat "Dimension records before: " (itoa (length *swapp-last-dimension-semantics-before*))))
                (swapp-int-write handle (strcat "Dimension records after: " (itoa (length *swapp-last-dimension-semantics-after*))))
                (swapp-int-write handle (strcat "Unmatched before: " (if unmatched-before unmatched-before "<none>")))
                (swapp-int-write handle (strcat "Same handle after: " (if same-handle-after same-handle-after "<none>")))
                (swapp-int-write handle (strcat "Unmatched after: " (if unmatched-after unmatched-after "<none>")))
                (swapp-int-write handle (strcat "Same handle before: " (if same-handle-before same-handle-before "<none>")))
              )
            )
            (swapp-int-write handle (strcat "Layout count: " (itoa layouts)))
            (swapp-int-write handle (strcat "Layout placement mode: " (if (swapp-state-value "LAYOUT_PLACEMENT_MODE") (swapp-state-value "LAYOUT_PLACEMENT_MODE") "<none>")))
            (swapp-int-write handle (strcat "Layout name policy: " (if (swapp-state-value "LAYOUT_NAME_POLICY") (swapp-state-value "LAYOUT_NAME_POLICY") "<none>")))
            (swapp-int-write handle (strcat "Owned layout count: " (if (swapp-state-value "LAYOUT_OWNED_COUNT") (swapp-state-value "LAYOUT_OWNED_COUNT") "<none>")))
            (swapp-int-write handle (strcat "Layout state plan count: " (if (swapp-state-value "LAYOUT_PLAN_COUNT") (swapp-state-value "LAYOUT_PLAN_COUNT") "<none>")))
            (swapp-int-write handle (strcat "Layout state signature: " (if (swapp-state-value "LAYOUT_PLAN_SIGNATURE") (swapp-state-value "LAYOUT_PLAN_SIGNATURE") "<none>")))
            (swapp-int-write handle (strcat "Title verify status: " title-status))
            (swapp-int-write handle (strcat "DIMSTYLE audit: " (swapp-int-bool dim-ok)))
            (swapp-int-write handle (strcat "Layout audit: " (swapp-int-bool layout-ok)))
            (swapp-int-write handle (strcat "Workflow stage: " stage))
            (setq pass
              (and
                command-ok
                (equal dim-state "OK")
                (equal (swapp-state-value "DIMENSION_SEMANTICS") "PRESERVED")
                (equal cleanup-state "OK")
                cleanup-ok
                (equal
                  (car definition-path-audit)
                  "DICT|NOD/SWCAD_WORKFLOW_STATE|XRECORD|<WORKFLOW-STATE-XRECORD>"
                )
                (= (cadr definition-path-audit) 0)
                (= (length layout-plan) 15)
                (= layouts 15)
                (equal (swapp-state-value "LAYOUT_PLACEMENT_MODE") *swapp-layout-placement-mode*)
                (equal (swapp-state-value "LAYOUT_PLAN_COUNT") "15")
                (equal (swapp-state-value "LAYOUT_PLAN_SIGNATURE") (swapp-layout-plan-signature layout-plan))
                (equal title-status "OK")
                dim-ok layout-ok
                (equal stage "COMPLETE")
              )
            )
          )
          ((equal mode "REOPEN")
            (setq stage (swapp-workflow-stage))
            (setq layouts (length (swapp-layout-owned-names)))
            (setq title-status (swcad-title-integrated-verify-final-summary))
            (setq dim-ok (swapp-dimstyle-verify))
            (setq cleanup-ok (swapp-resource-cleanup-verify))
            (setq definition-path-audit (swapp-int-definition-path-audit))
            (setq layout-ok (swapp-layout-state-valid-p (length (swcad-title-frame-records))))
            (setq verify-command-ok (swapp-int-command-ok 'c:SWCADVERIFY))
            (swapp-int-write handle (strcat "DIMSTYLE state: " (if (swapp-state-value "DIMSTYLE") (swapp-state-value "DIMSTYLE") "<none>")))
            (swapp-int-write handle (strcat "Dimension semantics: " (if (swapp-state-value "DIMENSION_SEMANTICS") (swapp-state-value "DIMENSION_SEMANTICS") "<none>")))
            (swapp-int-write handle (strcat "Dimension restore count: " (if (swapp-state-value "DIMENSION_RESTORE_COUNT") (swapp-state-value "DIMENSION_RESTORE_COUNT") "<none>")))
            (swapp-int-write handle (strcat "Resource cleanup state: " (if (swapp-state-value "RESOURCE_CLEANUP") (swapp-state-value "RESOURCE_CLEANUP") "<none>")))
            (swapp-int-write handle (strcat "Resource cleanup zero pass: " (if (swapp-state-value "RESOURCE_CLEANUP_ZERO_PASS") (swapp-state-value "RESOURCE_CLEANUP_ZERO_PASS") "<none>")))
            (swapp-int-write handle (strcat "Resource cleanup definition signature: " (if (swapp-state-value "RESOURCE_CLEANUP_DEFINITION_SIGNATURE") (swapp-state-value "RESOURCE_CLEANUP_DEFINITION_SIGNATURE") "<none>")))
            (swapp-int-write handle (strcat "Resource cleanup definition identity signature: " (if (swapp-state-value "RESOURCE_CLEANUP_DEFINITION_IDENTITY_SIGNATURE") (swapp-state-value "RESOURCE_CLEANUP_DEFINITION_IDENTITY_SIGNATURE") "<none>")))
            (swapp-int-write handle (strcat "Resource cleanup stable definition identity signature: " (if (swapp-state-value "RESOURCE_CLEANUP_STABLE_DEFINITION_IDENTITY_SIGNATURE") (swapp-state-value "RESOURCE_CLEANUP_STABLE_DEFINITION_IDENTITY_SIGNATURE") "<none>")))
            (swapp-int-write handle (strcat "Resource cleanup APPID identity signature: " (if (swapp-state-value "RESOURCE_CLEANUP_APPID_IDENTITY_SIGNATURE") (swapp-state-value "RESOURCE_CLEANUP_APPID_IDENTITY_SIGNATURE") "<none>")))
            (swapp-int-write handle (strcat "Resource cleanup VPORT identity signature: " (if (swapp-state-value "RESOURCE_CLEANUP_VPORT_IDENTITY_SIGNATURE") (swapp-state-value "RESOURCE_CLEANUP_VPORT_IDENTITY_SIGNATURE") "<none>")))
            (swapp-int-write handle (strcat "Resource cleanup session anonymous block identity signature: " (if (swapp-state-value "RESOURCE_CLEANUP_SESSION_ANON_BLOCK_IDENTITY_SIGNATURE") (swapp-state-value "RESOURCE_CLEANUP_SESSION_ANON_BLOCK_IDENTITY_SIGNATURE") "<none>")))
            (swapp-int-write handle (strcat "Resource cleanup state-save stabilization passes: " (if (swapp-state-value "RESOURCE_CLEANUP_STATE_SAVE_STABILIZATION_PASSES") (swapp-state-value "RESOURCE_CLEANUP_STATE_SAVE_STABILIZATION_PASSES") "<none>")))
            (swapp-int-write handle (strcat "Resource cleanup state-save rebase count: " (if (swapp-state-value "RESOURCE_CLEANUP_STATE_SAVE_REBASE_COUNT") (swapp-state-value "RESOURCE_CLEANUP_STATE_SAVE_REBASE_COUNT") "<none>")))
            (swapp-int-write handle (strcat "LAYOUT state: " (if (swapp-state-value "LAYOUT") (swapp-state-value "LAYOUT") "<none>")))
            (swapp-int-write handle (strcat "Layout placement mode: " (if (swapp-state-value "LAYOUT_PLACEMENT_MODE") (swapp-state-value "LAYOUT_PLACEMENT_MODE") "<none>")))
            (swapp-int-write handle (strcat "Layout name policy: " (if (swapp-state-value "LAYOUT_NAME_POLICY") (swapp-state-value "LAYOUT_NAME_POLICY") "<none>")))
            (swapp-int-write handle (strcat "Owned layout count: " (if (swapp-state-value "LAYOUT_OWNED_COUNT") (swapp-state-value "LAYOUT_OWNED_COUNT") "<none>")))
            (swapp-int-write handle (strcat "Layout state plan count: " (if (swapp-state-value "LAYOUT_PLAN_COUNT") (swapp-state-value "LAYOUT_PLAN_COUNT") "<none>")))
            (swapp-int-write handle (strcat "Layout state signature: " (if (swapp-state-value "LAYOUT_PLAN_SIGNATURE") (swapp-state-value "LAYOUT_PLAN_SIGNATURE") "<none>")))
            (swapp-int-write handle (strcat "Layout count: " (itoa layouts)))
            (swapp-int-write handle (strcat "Title verify status: " title-status))
            (swapp-int-write handle (strcat "DIMSTYLE audit: " (swapp-int-bool dim-ok)))
            (swapp-int-write handle (strcat "Resource cleanup audit: " (swapp-int-bool cleanup-ok)))
            (swapp-int-write handle (strcat "Workflow state definition record: " (car definition-path-audit)))
            (swapp-int-write handle (strcat "Definition <NO-KEY> count: " (itoa (cadr definition-path-audit))))
            (swapp-int-write handle (strcat "Layout audit: " (swapp-int-bool layout-ok)))
            (swapp-int-write handle (strcat "Public SWCADVERIFY returned without error: " (swapp-int-bool verify-command-ok)))
            (swapp-int-write handle (strcat "Workflow stage: " stage))
            (swapp-int-write handle (strcat "DBMOD after: " (itoa (getvar "DBMOD"))))
            (setq pass
              (and
                (equal (swapp-state-value "DIMSTYLE") "OK")
                (equal (swapp-state-value "DIMENSION_SEMANTICS") "PRESERVED")
                (equal (swapp-state-value "RESOURCE_CLEANUP") "OK")
                cleanup-ok
                (equal
                  (car definition-path-audit)
                  "DICT|NOD/SWCAD_WORKFLOW_STATE|XRECORD|<WORKFLOW-STATE-XRECORD>"
                )
                (= (cadr definition-path-audit) 0)
                (equal (swapp-state-value "LAYOUT") "OK")
                (equal (swapp-state-value "LAYOUT_PLACEMENT_MODE") *swapp-layout-placement-mode*)
                (equal (swapp-state-value "LAYOUT_PLAN_COUNT") "15")
                (equal (swapp-state-value "LAYOUT_PLAN_SIGNATURE") (swapp-layout-plan-signature (swapp-layout-plan)))
                (= layouts 15)
                (equal title-status "OK")
                dim-ok layout-ok verify-command-ok
                (equal stage "COMPLETE")
                (= (getvar "DBMOD") 0)
              )
            )
          )
          (T
            (swapp-int-write handle "Unknown integration probe mode.")
            (setq pass nil)
          )
        )
        (progn
          (swapp-int-write handle (strcat "Load error: " (vl-catch-all-error-message load-result)))
          (setq pass nil)
        )
      )
      (swapp-int-write handle (strcat "Runtime check completed: " (swapp-int-bool pass)))
    )
  )
  (princ)
)

(swapp-int-main)
