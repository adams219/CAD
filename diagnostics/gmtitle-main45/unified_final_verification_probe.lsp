;;; Read-only verification for a saved/reopened 15-sheet unified GMTITLE result.

(defun swtitle-final-probe-root (/ root)
  (setq root (getenv "SWCAD_TOOL_ROOT"))
  (if (or (not root) (= (strlen root) 0))
    (setq root "C:/Users/DR-DESIGN/Documents/CAD tool")
  )
  (vl-string-translate "\\" "/" root)
)

(defun swtitle-final-probe-path (relative)
  (strcat (swtitle-final-probe-root) "/" relative)
)

(defun swtitle-final-probe-write (handle value)
  (write-line (if value value "") handle)
)

(defun swtitle-final-probe-count (key counts)
  (if (assoc key counts) (cdr (assoc key counts)) 0)
)

(defun swtitle-final-probe-value (tag values)
  (if (assoc tag values)
    (swcad-title-normalized-field-value (cdr (assoc tag values)))
    "<missing>"
  )
)

(defun swtitle-final-probe-values-match-p (actual expected / ok pair)
  (setq ok T)
  (foreach pair expected
    (if (/= (swtitle-final-probe-value (car pair) actual) (swcad-title-normalized-field-value (cdr pair)))
      (setq ok nil)
    )
  )
  ok
)

(defun swtitle-final-probe-a4-expected-values (drawing-number)
  (if (equal drawing-number "DRP125 CP_PL 2nd_260529_310")
    '(
      ("GEN-TITLE-QTY{10}" . "")
      ("GEN-TITLE-MAT1{10}" . "")
      ("GEN-TITLE-NAME{10}" . "HS.KANG")
      ("GEN-TITLE-CHKM{10}" . "HS.KANG")
      ("GEN-TITLE-APPM{21.7}" . "KS. LEE")
      ("GEN-TITLE-DATE{11.7}" . "20260601")
      ("GEN-TITLE-SCA{6.7}" . "2:1")
      ("GEN-TITLE-DWG{23}" . "DRP125 CP_PL 2nd_260529")
      ("GEN-TITLE-NR{23}" . "DRP125 CP_PL 2nd_260529_310")
      ("GEN-TITLE-REV{5}" . "0")
      ("GEN-TITLE-SIZ{6.7}" . "A4")
    )
    (if (equal drawing-number "DRP125 CP_PL 1st_260529_302")
      '(
        ("GEN-TITLE-QTY{10}" . "")
        ("GEN-TITLE-MAT1{10}" . "")
        ("GEN-TITLE-NAME{10}" . "HS.KANG")
        ("GEN-TITLE-CHKM{10}" . "HS.KANG")
        ("GEN-TITLE-APPM{21.7}" . "KS.LEE")
        ("GEN-TITLE-DATE{11.7}" . "2026-06-01")
        ("GEN-TITLE-SCA{6.7}" . "2 : 1")
        ("GEN-TITLE-DWG{23}" . "DRP125 CP_PL 1st_260529")
        ("GEN-TITLE-NR{23}" . "DRP125 CP_PL 1st_260529_302")
        ("GEN-TITLE-REV{5}" . "0")
        ("GEN-TITLE-SIZ{6.7}" . "A4")
      )
      nil
    )
  )
)

(defun swtitle-final-probe-existing-handle-count (handles / count item)
  (setq count 0)
  (foreach item handles
    (if (handent item) (setq count (+ count 1)))
  )
  count
)

(defun swtitle-final-probe-main (/ *error* load-result load-ok log-path handle dbmod-before dbmod-after version verify-result verify-status summary source-title-count source-frame-count frame-only-count target-frame-counts target-title-count pair-records pair-count native-like-count target-shell-count orphan-count duplicate-count upgrade-count stored-title-counts a4-pair-count a4-attribute-match-count a4-loose-title-count a4-combined-approval-date-count record frame-block frame-bbox title-ename title-object actual-values drawing-number expected-values approved-pair loose-records old-title-handles old-shell-handles protected-note-handles old-title-handle-count old-shell-handle-count protected-note-count all-good)
  (setq dbmod-before (getvar "DBMOD"))
  (setq load-result
    (vl-catch-all-apply
      'load
      (list (swtitle-final-probe-path "src/tools/gmtitle/swcad_title_scale.lsp"))
    )
  )
  (setq load-ok (not (vl-catch-all-error-p load-result)))
  (setq log-path (getenv "SWCAD_UNIFIED_FINAL_VERIFY_LOG"))
  (if (or (not log-path) (= (strlen log-path) 0))
    (setq log-path (swtitle-final-probe-path "work/swtitle_unified_final_verification_probe.txt"))
  )
  (setq log-path (vl-string-translate "\\" "/" log-path))
  (setq handle (open log-path "w"))
  (if handle
    (progn
      (defun *error* (msg)
        (if handle
          (progn
            (swtitle-final-probe-write handle (strcat "Probe runtime error: " (if msg msg "<unknown>")))
            (swtitle-final-probe-write handle "Probe result: FAIL")
            (swtitle-final-probe-write handle "Runtime check completed: yes")
            (close handle)
            (setq handle nil)
          )
        )
        (princ)
      )
      (swtitle-final-probe-write handle "SWTITLE unified final read-only verification probe")
      (swtitle-final-probe-write handle (strcat "DWG: " (getvar "DWGPREFIX") (getvar "DWGNAME")))
      (swtitle-final-probe-write handle (strcat "DBMOD before: " (itoa dbmod-before)))
      (if load-ok
        (progn
          (setq version (if (boundp '*swcad-title-scale-version*) *swcad-title-scale-version* "<missing>"))
          (setq verify-result (vl-catch-all-apply 'swcad-title-integrated-verify-final-summary nil))
          (setq verify-status (if (boundp '*swcad-title-last-apply-status*) *swcad-title-last-apply-status* "<missing>"))
          (setq summary (swcad-title-fast-sheet-summary))
          (setq source-title-count (swcad-title-fast-summary-value summary "source-title-count"))
          (setq source-frame-count (swcad-title-fast-summary-value summary "source-frame-count"))
          (setq frame-only-count (swcad-title-fast-summary-value summary "frame-only-count"))
          (setq target-frame-counts (swcad-title-target-frame-sheet-counts))
          (setq target-title-count (swcad-title-count-inserts-by-effective-name (swcad-title-target-title-block-name)))
          (setq pair-records (swcad-title-target-gmtitle-pair-records))
          (setq pair-count (length pair-records))
          (setq target-shell-count (length (swcad-title-target-title-shell-records)))
          (setq native-like-count 0)
          (setq a4-pair-count 0)
          (setq a4-attribute-match-count 0)
          (setq a4-loose-title-count 0)
          (setq a4-combined-approval-date-count 0)
          (foreach record pair-records
            (if (swcad-title-target-pair-native-like-p record)
              (setq native-like-count (+ native-like-count 1))
            )
            (setq frame-block (nth 2 record))
            (if (equal (swcad-title-normalized-sheet-size (swcad-title-sheet-size-from-block-name frame-block)) "A4")
              (progn
                (setq a4-pair-count (+ a4-pair-count 1))
                (setq title-ename (car record))
                (setq title-object (swcad-title-safe-vla-object title-ename))
                (setq actual-values (swcad-title-title-attribute-pairs title-object))
                (setq approved-pair (assoc "GEN-TITLE-APPM{21.7}" actual-values))
                (if
                  (and
                    approved-pair
                    (swcad-title-combined-approval-date-split (cdr approved-pair))
                  )
                  (setq a4-combined-approval-date-count (+ a4-combined-approval-date-count 1))
                )
                (setq drawing-number (swtitle-final-probe-value "GEN-TITLE-NR{23}" actual-values))
                (setq expected-values (swtitle-final-probe-a4-expected-values drawing-number))
                (if (and expected-values (swtitle-final-probe-values-match-p actual-values expected-values))
                  (setq a4-attribute-match-count (+ a4-attribute-match-count 1))
                )
                (setq frame-bbox (nth 4 record))
                (setq loose-records
                  (swcad-title-transfer-text-records
                    (swcad-title-loose-title-region-bbox frame-bbox)
                    nil
                  )
                )
                (setq a4-loose-title-count (+ a4-loose-title-count (length loose-records)))
                (swtitle-final-probe-write
                  handle
                  (strcat
                    "A4 pair #" (itoa a4-pair-count)
                    ": drawing-number=" drawing-number
                    ", attributes-match=" (if (and expected-values (swtitle-final-probe-values-match-p actual-values expected-values)) "yes" "no")
                    ", loose-title-texts=" (itoa (length loose-records))
                  )
                )
              )
            )
          )
          (setq orphan-count (length (swcad-title-orphan-target-frame-records)))
          (setq duplicate-count (length (swcad-title-duplicate-target-pair-records)))
          (setq upgrade-count (length (swcad-title-a3a4-native-upgrade-candidate-records)))
          (setq stored-title-counts (swcad-title-stored-expected-title-counts))
          (setq old-title-handles '("36F5" "36F4" "36F3" "36F2" "36F1" "36F0" "36EF" "36EE" "36ED" "52A2" "52A1" "52A0" "529F" "529E" "529D" "529C" "529B" "529A"))
          (setq old-shell-handles '("36E5" "5292"))
          (setq protected-note-handles '("36EB" "36EA" "36E9" "36E8" "5299" "5298" "5297" "5296"))
          (setq old-title-handle-count (swtitle-final-probe-existing-handle-count old-title-handles))
          (setq old-shell-handle-count (swtitle-final-probe-existing-handle-count old-shell-handles))
          (setq protected-note-count (swtitle-final-probe-existing-handle-count protected-note-handles))
          (setq dbmod-after (getvar "DBMOD"))
          (setq all-good
            (and
              (not (vl-catch-all-error-p verify-result))
                  (equal version "260713-frame-style-structure-guard-1")
              (equal verify-status "SWTITLEVERIFY_FINAL_OK")
              (= source-title-count 0)
              (= source-frame-count 0)
              (= frame-only-count 0)
              (= target-title-count 15)
              (= pair-count 15)
              (= native-like-count 15)
              (= target-shell-count 0)
              (= (swtitle-final-probe-count "A2" target-frame-counts) 1)
              (= (swtitle-final-probe-count "A3" target-frame-counts) 12)
              (= (swtitle-final-probe-count "A4" target-frame-counts) 2)
              (= (swtitle-final-probe-count "A2" stored-title-counts) 1)
              (= (swtitle-final-probe-count "A3" stored-title-counts) 12)
              (= (swtitle-final-probe-count "A4" stored-title-counts) 2)
              (= a4-pair-count 2)
              (= a4-attribute-match-count 2)
              (= a4-combined-approval-date-count 0)
              (= a4-loose-title-count 0)
              (= old-title-handle-count 0)
              (= old-shell-handle-count 0)
              (= protected-note-count 8)
              (= orphan-count 0)
              (= duplicate-count 0)
              (= upgrade-count 0)
              (= dbmod-before 0)
              (= dbmod-after 0)
            )
          )
          (swtitle-final-probe-write handle (strcat "Loaded version: " version))
          (swtitle-final-probe-write handle (strcat "SWTITLEVERIFY status: " verify-status))
          (swtitle-final-probe-write handle (strcat "Remaining source titles/frames/frame-only: " (itoa source-title-count) "/" (itoa source-frame-count) "/" (itoa frame-only-count)))
          (swtitle-final-probe-write handle (strcat "Target title/frame-pair/native-like: " (itoa target-title-count) "/" (itoa pair-count) "/" (itoa native-like-count)))
          (swtitle-final-probe-write handle (strcat "Target title-overlapping source shell inserts: " (itoa target-shell-count)))
          (swtitle-final-probe-write handle (strcat "Target frame counts: A2=" (itoa (swtitle-final-probe-count "A2" target-frame-counts)) ", A3=" (itoa (swtitle-final-probe-count "A3" target-frame-counts)) ", A4=" (itoa (swtitle-final-probe-count "A4" target-frame-counts))))
          (swtitle-final-probe-write handle (strcat "Stored expected title counts: A2=" (itoa (swtitle-final-probe-count "A2" stored-title-counts)) ", A3=" (itoa (swtitle-final-probe-count "A3" stored-title-counts)) ", A4=" (itoa (swtitle-final-probe-count "A4" stored-title-counts))))
          (swtitle-final-probe-write handle (strcat "A4 attribute match count: " (itoa a4-attribute-match-count)))
          (swtitle-final-probe-write handle (strcat "A4 combined approval/date values: " (itoa a4-combined-approval-date-count)))
          (swtitle-final-probe-write handle (strcat "A4 remaining loose title texts: " (itoa a4-loose-title-count)))
          (swtitle-final-probe-write handle (strcat "Original A4 loose title handles remaining: " (itoa old-title-handle-count)))
          (swtitle-final-probe-write handle (strcat "Original A4 title shell handles remaining: " (itoa old-shell-handle-count)))
          (swtitle-final-probe-write handle (strcat "Protected A4 note handles remaining: " (itoa protected-note-count)))
          (swtitle-final-probe-write handle (strcat "Orphan/duplicate/upgrade candidates: " (itoa orphan-count) "/" (itoa duplicate-count) "/" (itoa upgrade-count)))
          (swtitle-final-probe-write handle (strcat "DBMOD after: " (itoa dbmod-after)))
          (swtitle-final-probe-write handle (strcat "Probe result: " (if all-good "PASS" "FAIL")))
        )
        (progn
          (swtitle-final-probe-write handle (strcat "Load result: ERROR - " (vl-catch-all-error-message load-result)))
          (swtitle-final-probe-write handle "Probe result: FAIL")
        )
      )
      (swtitle-final-probe-write handle "Runtime check completed: yes")
      (close handle)
      (setq handle nil)
    )
  )
  (princ)
)

(swtitle-final-probe-main)
