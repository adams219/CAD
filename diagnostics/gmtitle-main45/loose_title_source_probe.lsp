;;; Read-only regression probe for mixed title sources in the real 15-sheet fixture.
;;; The PowerShell wrapper runs this against a disposable DWG copy and checks hashes.

(defun swtitle-loose-probe-root (/ root)
  (setq root (getenv "SWCAD_TOOL_ROOT"))
  (if (or (not root) (= (strlen root) 0))
    (setq root "C:/Users/DR-DESIGN/Documents/CAD tool")
  )
  (vl-string-translate "\\" "/" root)
)

(defun swtitle-loose-probe-path (relative)
  (strcat (swtitle-loose-probe-root) "/" relative)
)

(defun swtitle-loose-probe-write (handle value)
  (write-line (if value value "") handle)
)

(defun swtitle-loose-probe-count (key counts)
  (if (assoc key counts) (cdr (assoc key counts)) 0)
)

(defun swtitle-loose-probe-relative-bbox (bbox left bottom right top)
  (list
    (list (+ (car (car bbox)) left) (+ (cadr (car bbox)) bottom))
    (list (+ (car (cadr bbox)) right) (+ (cadr (car bbox)) top))
  )
)

(defun swtitle-loose-probe-mapped-handle-p (handle mappings / found mapping)
  (setq found nil)
  (foreach mapping mappings
    (if (equal (strcase (swcad-title-string handle)) (strcase (swcad-title-string (cadddr mapping))))
      (setq found T)
    )
  )
  found
)

(defun swtitle-loose-probe-main (/ *error* load-result load-ok log-path handle dbmod-before dbmod-after version summary title-counts sources source source-kind insert-count loose-count loose-a4-count title-bbox build mappings mapping records unmapped duplicates values date-pair approved-pair raw-approved-mapping raw-approved normalized-approved approval-normalized-count combined-approval-date-remaining companion-records companion-total protected-note-handles protected-note-count note-handle note-overlap-count mapped-total unmapped-total duplicate-total all-good index)
  (setq dbmod-before (getvar "DBMOD"))
  (setq load-result
    (vl-catch-all-apply
      'load
      (list (swtitle-loose-probe-path "src/tools/gmtitle/swcad_title_scale.lsp"))
    )
  )
  (setq load-ok (not (vl-catch-all-error-p load-result)))
  (setq log-path (getenv "SWCAD_LOOSE_TITLE_SOURCE_LOG"))
  (if (or (not log-path) (= (strlen log-path) 0))
    (setq log-path (swtitle-loose-probe-path "work/swtitle_loose_title_source_probe.txt"))
  )
  (setq log-path (vl-string-translate "\\" "/" log-path))
  (setq handle (open log-path "w"))
  (if handle
    (progn
      (defun *error* (msg)
        (if handle
          (progn
            (swtitle-loose-probe-write handle (strcat "Probe runtime error: " (if msg msg "<unknown>")))
            (swtitle-loose-probe-write handle "Probe result: FAIL")
            (swtitle-loose-probe-write handle "Runtime check completed: yes")
            (close handle)
            (setq handle nil)
          )
        )
        (princ)
      )
      (swtitle-loose-probe-write handle "SWTITLE loose-title source regression probe")
      (swtitle-loose-probe-write handle (strcat "DWG: " (getvar "DWGPREFIX") (getvar "DWGNAME")))
      (swtitle-loose-probe-write handle (strcat "DBMOD before: " (itoa dbmod-before)))
      (if load-ok
        (progn
          (setq version (if (boundp '*swcad-title-scale-version*) *swcad-title-scale-version* "<missing>"))
          (swtitle-loose-probe-write handle (strcat "Load result: OK, version=" version))
          (setq summary (swcad-title-fast-sheet-summary))
          (swtitle-loose-probe-write handle "Progress: fast sheet summary complete")
          (setq title-counts (swcad-title-fast-summary-value summary "title-sheet-counts"))
          (setq sources (swcad-title-source-title-candidates))
          (swtitle-loose-probe-write handle "Progress: source title candidate scan complete")
          (setq insert-count 0)
          (setq loose-count 0)
          (setq loose-a4-count 0)
          (setq mapped-total 0)
          (setq unmapped-total 0)
          (setq duplicate-total 0)
          (setq companion-total 0)
          (setq approval-normalized-count 0)
          (setq combined-approval-date-remaining 0)
          (setq note-overlap-count 0)
          (setq protected-note-handles '("36EB" "36EA" "36E9" "36E8" "5299" "5298" "5297" "5296"))
          (setq protected-note-count 0)
          (foreach note-handle protected-note-handles
            (if (handent note-handle)
              (setq protected-note-count (+ protected-note-count 1))
            )
          )
          (setq all-good T)
          (setq index 0)
          (foreach source sources
            (setq source-kind (swcad-title-source-title-kind source))
            (if (equal source-kind "loose-text")
              (progn
                (setq loose-count (+ loose-count 1))
                (if (equal (swcad-title-normalized-sheet-size (nth 9 source)) "A4")
                  (setq loose-a4-count (+ loose-a4-count 1))
                )
                (setq index (+ index 1))
                (setq title-bbox (caddr source))
                (setq build (swcad-title-transfer-build-mappings title-bbox nil 7.0))
                (setq mappings (car build))
                (setq records (cadr build))
                (setq unmapped (caddr build))
                (setq duplicates (cadddr build))
                (setq values (swcad-title-transfer-values mappings))
                (setq date-pair (assoc "GEN-TITLE-DATE{11.7}" values))
                (setq approved-pair (assoc "GEN-TITLE-APPM{21.7}" values))
                (setq raw-approved-mapping (assoc "GEN-TITLE-APPM{21.7}" mappings))
                (setq raw-approved
                  (if raw-approved-mapping
                    (swcad-title-string (nth 2 (cdr raw-approved-mapping)))
                    ""
                  )
                )
                (setq normalized-approved (if approved-pair (swcad-title-string (cdr approved-pair)) ""))
                (if (/= raw-approved normalized-approved)
                  (setq approval-normalized-count (+ approval-normalized-count 1))
                )
                (if (swcad-title-combined-approval-date-split normalized-approved)
                  (setq combined-approval-date-remaining (+ combined-approval-date-remaining 1))
                )
                (setq companion-records
                  (swcad-title-source-title-shell-records
                    title-bbox
                    nil
                    (nth 6 source)
                  )
                )
                (setq companion-total (+ companion-total (length companion-records)))
                (setq mapped-total (+ mapped-total (length mappings)))
                (setq unmapped-total (+ unmapped-total (length unmapped)))
                (setq duplicate-total (+ duplicate-total (length duplicates)))
                (foreach mapping mappings
                  (if (member (strcase (swcad-title-string (cadddr mapping))) protected-note-handles)
                    (setq note-overlap-count (+ note-overlap-count 1))
                  )
                )
                (if (or
                      (/= (length records) 9)
                      (/= (length mappings) 9)
                      (/= (length unmapped) 0)
                      (/= (length duplicates) 0)
                      (not date-pair)
                      (= (strlen (vl-string-trim " \t\r\n" (swcad-title-string (cdr date-pair)))) 0)
                      (/= (length companion-records) 1)
                    )
                  (setq all-good nil)
                )
                (swtitle-loose-probe-write
                  handle
                  (strcat
                    "Loose A4 #" (itoa index)
                    ": records=" (itoa (length records))
                    ", mapped=" (itoa (length mappings))
                    ", unmapped=" (itoa (length unmapped))
                    ", duplicates=" (itoa (length duplicates))
                    ", companion-shells=" (itoa (length companion-records))
                    ", approved=" normalized-approved
                    ", date=" (if date-pair (swcad-title-string (cdr date-pair)) "<missing>")
                  )
                )
              )
              (setq insert-count (+ insert-count 1))
            )
          )
          (setq dbmod-after (getvar "DBMOD"))
          (setq all-good
            (and
              all-good
              (equal version "260713-frame-style-structure-guard-1")
              (= (swcad-title-fast-summary-value summary "source-title-count") 15)
              (= (swcad-title-fast-summary-value summary "source-frame-count") 15)
              (= (swcad-title-fast-summary-value summary "frame-only-count") 0)
              (= (swtitle-loose-probe-count "A2" title-counts) 1)
              (= (swtitle-loose-probe-count "A3" title-counts) 12)
              (= (swtitle-loose-probe-count "A4" title-counts) 2)
              (= insert-count 13)
              (= loose-count 2)
              (= loose-a4-count 2)
              (= mapped-total 18)
              (= unmapped-total 0)
              (= duplicate-total 0)
              (= companion-total 2)
              (= approval-normalized-count 1)
              (= combined-approval-date-remaining 0)
              (= protected-note-count 8)
              (= note-overlap-count 0)
              (= dbmod-before 0)
              (= dbmod-after 0)
            )
          )
          (swtitle-loose-probe-write handle (strcat "Loaded version: " version))
          (swtitle-loose-probe-write handle (strcat "Source title count: " (itoa (swcad-title-fast-summary-value summary "source-title-count"))))
          (swtitle-loose-probe-write handle (strcat "Source frame count: " (itoa (swcad-title-fast-summary-value summary "source-frame-count"))))
          (swtitle-loose-probe-write handle (strcat "Frame-only count: " (itoa (swcad-title-fast-summary-value summary "frame-only-count"))))
          (swtitle-loose-probe-write handle (strcat "Title sheet counts: A2=" (itoa (swtitle-loose-probe-count "A2" title-counts)) ", A3=" (itoa (swtitle-loose-probe-count "A3" title-counts)) ", A4=" (itoa (swtitle-loose-probe-count "A4" title-counts))))
          (swtitle-loose-probe-write handle (strcat "Title source kinds: block-attributes=" (itoa insert-count) ", loose-text=" (itoa loose-count)))
          (swtitle-loose-probe-write handle (strcat "A4 loose-title sources: " (itoa loose-a4-count)))
          (swtitle-loose-probe-write handle (strcat "Mapping totals: mapped=" (itoa mapped-total) ", unmapped=" (itoa unmapped-total) ", duplicates=" (itoa duplicate-total)))
          (swtitle-loose-probe-write handle (strcat "Loose-title companion shell inserts: " (itoa companion-total)))
          (swtitle-loose-probe-write handle (strcat "A4 combined approval/date normalized: " (itoa approval-normalized-count)))
          (swtitle-loose-probe-write handle (strcat "A4 combined approval/date remaining: " (itoa combined-approval-date-remaining)))
          (swtitle-loose-probe-write handle (strcat "Protected notes outside title region: " (itoa protected-note-count)))
          (swtitle-loose-probe-write handle (strcat "Protected note handles used as title mappings: " (itoa note-overlap-count)))
          (swtitle-loose-probe-write handle (strcat "DBMOD after: " (itoa dbmod-after)))
          (swtitle-loose-probe-write handle (strcat "Probe result: " (if all-good "PASS" "FAIL")))
        )
        (progn
          (swtitle-loose-probe-write handle (strcat "Load result: ERROR - " (vl-catch-all-error-message load-result)))
          (swtitle-loose-probe-write handle "Probe result: FAIL")
        )
      )
      (swtitle-loose-probe-write handle "Runtime check completed: yes")
      (close handle)
    )
  )
  (princ)
)

(swtitle-loose-probe-main)
