;;; Probe for the GMTITLE value fix on a throw-away copy (never saved):
;;; 1. unit checks of swcad-title-complete-title-values / swcad-title-mtext-plain;
;;; 2. for all 30 source sheets, writes the planned 11 values into one attributed
;;;    DR_titlea_3rd-like insert, reads them back and runs the value verification.
;;; Environment: SWT_WRITE_LOG = log path, SWT_PLAN_MODULE = swcad_title_scale.lsp path.

(vl-load-com)
(load (getenv "SWT_PLAN_MODULE"))

(defun swt-w-line (log parts / text part)
  (setq text "")
  (foreach part parts
    (setq text (strcat text (if (= text "") "" "|") (vl-string-translate "|\n\r\t" "/   " (swcad-title-string part))))
  )
  (write-line text log)
)

(defun swt-w-target (/ ss idx obj result)
  (setq ss (ssget "_X" '((0 . "INSERT") (66 . 1))))
  (setq idx 0)
  (setq result nil)
  (if ss
    (while (and (not result) (< idx (sslength ss)))
      (setq obj (vlax-ename->vla-object (ssname ss idx)))
      (if (wcmatch (strcase (swcad-title-vla-block-name obj)) "*DR_TITLEA_3RD")
        (setq result obj)
      )
      (setq idx (1+ idx))
    )
  )
  result
)

(defun swt-w-check (log label actual expected)
  (swt-w-line log (list (if (equal actual expected) "UNIT_OK" "UNIT_FAIL") label actual expected))
)

(defun swt-w-units (log target / today final)
  (setq today (swcad-title-today-date-string))
  (swt-w-line log (list "TODAY" today))
  (swt-w-check log "plain-font-code" (swcad-title-mtext-plain "{\\FTXT,bigfont|c129;P_eCVT-ICL Gear_RH_260506}") "P_eCVT-ICL Gear_RH_260506")
  (swt-w-check log "plain-width-code" (swcad-title-mtext-plain "{\\W0.7;P_eCVT-Cage Rotor Adapter_260526_1900}") "P_eCVT-Cage Rotor Adapter_260526_1900")
  (swt-w-check log "plain-korean" (swcad-title-mtext-plain "{\\f굴림|b0|i0|c129|p32;재질 \\FTXT,bigfont|c0;: PEEK}") "재질 : PEEK")
  (swt-w-check log "plain-paragraph" (swcad-title-mtext-plain "MOTOR\\PMOUNT") "MOTOR MOUNT")
  (swt-w-check log "plain-stack" (swcad-title-mtext-plain "\\S1^2;") "1/2")
  (swt-w-check log "plain-escapes" (swcad-title-mtext-plain "A\\\\B \\{x\\}") "A\\B {x}")
  (swt-w-check log "plain-keep-codes" (swcad-title-mtext-plain "%%c10 \\U+2205") "%%c10 \\U+2205")
  (swt-w-check log "plain-toggles" (swcad-title-mtext-plain "\\Lunder\\l \\Oover\\o") "under over")
  (swt-w-check log "plain-plain-text" (swcad-title-mtext-plain "  SS400  ") "SS400")
  (setq final
    (swcad-title-complete-title-values
      (list
        (cons "GEN-TITLE-NR{23}" "XXX")
        (cons "GEN-TITLE-DWG{23}" "C:\\Program Files\\Some Folder\\part.dwg")
        (cons "GEN-TITLE-NAME{10}" "")
        (cons "GEN-TITLE-DATE{11.7}" "2024-00-00")
        (cons "GEN-TITLE-CHKM{10}" "  J PARK ")
        (cons "GEN-TITLE-MAT1{10}" "{\\f굴림|b0|i0|c129|p32;SUS304}")
        (cons "GEN-TITLE-SIZ{6.7}" "A3")
      )
      target
    )
  )
  (swt-w-check log "complete-count" (itoa (length final)) "11")
  (swt-w-check log "complete-NR-XXX" (cdr (assoc "GEN-TITLE-NR{23}" final)) "")
  (swt-w-check log "complete-DWG-path" (cdr (assoc "GEN-TITLE-DWG{23}" final)) "")
  (swt-w-check log "complete-NAME-empty" (cdr (assoc "GEN-TITLE-NAME{10}" final)) "HS KANG")
  (swt-w-check log "complete-DATE-placeholder" (cdr (assoc "GEN-TITLE-DATE{11.7}" final)) today)
  (swt-w-check log "complete-CHKM-trim" (cdr (assoc "GEN-TITLE-CHKM{10}" final)) "J PARK")
  (swt-w-check log "complete-APPM-missing" (cdr (assoc "GEN-TITLE-APPM{21.7}" final)) "KS LEE")
  (swt-w-check log "complete-SCA-missing" (cdr (assoc "GEN-TITLE-SCA{6.7}" final)) "1:1")
  (swt-w-check log "complete-REV-missing" (cdr (assoc "GEN-TITLE-REV{5}" final)) "0")
  (swt-w-check log "complete-QTY-missing" (cdr (assoc "GEN-TITLE-QTY{10}" final)) "1")
  (swt-w-check log "complete-MAT1-code" (cdr (assoc "GEN-TITLE-MAT1{10}" final)) "SUS304")
  (swt-w-check log "complete-SIZ" (cdr (assoc "GEN-TITLE-SIZ{6.7}" final)) "A3")
  (swt-w-check log "complete-SIZ-missing" (cdr (assoc "GEN-TITLE-SIZ{6.7}" (swcad-title-complete-title-values nil target))) "")
  (swt-w-check log "problems-XXX" (caddr (car (swcad-title-title-value-problems (list (cons "GEN-TITLE-NR{23}" "XXX"))))) "placeholder-XXX")
  (swt-w-check log "problems-path" (caddr (car (swcad-title-title-value-problems (list (cons "GEN-TITLE-DWG{23}" "C:\\Program Files\\a.dwg"))))) "file-path")
  (swt-w-check log "problems-code" (caddr (car (swcad-title-title-value-problems (list (cons "GEN-TITLE-NR{23}" "\\FTXT,bigfont|c129;P_eCVT"))))) "format-code")
  (swt-w-check log "problems-clean" (itoa (length (swcad-title-title-value-problems (list (cons "GEN-TITLE-NR{23}" "P_eCVT-Motor Gear 20T_260506") (cons "GEN-TITLE-DWG{23}" "5560 Shaft Spacer_PEEK_260526.DWG") (cons "GEN-TITLE-MAT1{10}" "%%c10 H7"))))) "0")
)

(defun swt-w-main (/ log target records index item source source-ename source-bbox source-block source-frame source-frame-ename source-frame-bbox source-frame-block build values block-sheet final attr-count errors total-errors pair planned)
  (setq log (open (getenv "SWT_WRITE_LOG") "w"))
  (setq target (swt-w-target))
  (swt-w-line log (list "TARGET" (if target (strcat (vla-get-Handle target) " " (swcad-title-vla-block-name target)) "<none>")))
  (swt-w-units log target)
  (setq records (swcad-title-transfer-batch-source-records))
  (setq index 0)
  (setq total-errors 0)
  ;; Pass 1: plan every sheet before anything is written, because the write target
  ;; is itself one of the source titles.
  (setq planned nil)
  (foreach item records
    (setq index (1+ index))
    (setq source (car item))
    (setq source-ename (car source))
    (setq source-bbox (caddr source))
    (setq source-block (if source-ename (swcad-title-effective-insert-name source-ename) ""))
    (setq source-frame (if source-bbox (swcad-title-transfer-source-frame source-bbox source-ename) nil))
    (setq source-frame-ename (if source-frame (car source-frame) nil))
    (setq source-frame-block (if source-frame-ename (swcad-title-effective-insert-name source-frame-ename) nil))
    (setq build (swcad-title-transfer-build-mappings source-bbox source-ename 7.0))
    (setq values (swcad-title-transfer-values (car build)))
    (if (not source-ename)
      (setq values (swcad-title-values-fill-missing-template-empty values))
    )
    (setq block-sheet (swcad-title-source-block-sheet-size source-block source-frame-block))
    (setq values (swcad-title-values-with-sheet-size-override values block-sheet))
    (setq planned (append planned (list values)))
  )
  ;; Pass 2: the same three calls as the transfer: complete, write, verify.
  (setq index 0)
  (foreach values planned
    (setq index (1+ index))
    (setq final (swcad-title-complete-title-values values target))
    (setq attr-count (swcad-title-set-insert-attributes target final))
    (setq errors (swcad-title-value-verification-errors target final))
    (setq total-errors (+ total-errors (length errors)))
    (swt-w-line log (list "WRITE" (itoa index) (itoa attr-count) (itoa (length errors))))
    (foreach pair (swcad-title-title-attribute-pairs target)
      (swt-w-line log (list "READBACK" (itoa index) (car pair) (cdr pair)))
    )
    (foreach pair errors
      (swt-w-line log (list "ERROR" (itoa index) (car pair) (cadr pair) (caddr pair)))
    )
  )
  (swt-w-line log (list "TOTAL_ERRORS" (itoa total-errors)))
  (write-line "Write verify probe completed: yes" log)
  (close log)
  (princ)
)

(swt-w-main)
